module test-module {
	namespace "urn:tester:one";
	prefix "tmo";

	import test-import-module {
		prefix "imp";
	}

	organization "";
	contact "";
	description "";

	revision 2015-05-30 {
		description "initial";
		reference "testing";
	}

	typedef percent {
		type uint8 {
			range "0 .. 100";
		}
		description "Percentage";
	}

    typedef name {
        type string;
    }

	container topcontainer {
		container simplecontainer {
			description "";
			leaf simpleleaf {
				type string;
				description "";
			}
		}

		choice shallowchoice {
			container erstcase {
				leaf erstcaseleaf {
					type string;
				}
			}
			container zwei {
				leaf zweicaseleaf {
					type string;
				}
			}
			leaf thirdbutleaf {
				type string;
			}
		}

        choice achoice {
            case firstcasecase {
                container firstcase {
                    leaf firstcaseleaf {
                        type string;
                    }
                }
            }
            case secondcasecase {
                container secondcontainer {
                    leaf secondcaseleaf {
                        type string;
                    }
                }
                leaf topsecondcaseleaf {
                    type string;
                }
            }
        }

		container maincontainer {
			description "";		
			list mainlist {
				key first;

				description "";

                leaf aleafref {
                    type leafref {
                        path "../first";
                    }
                }

				leaf first {
					type string;
					description "";
				}
				leaf second {
					type string;
					description "";
				}
				leaf third {
					type string;
					description "";
				}

				container containerinlist {
					description "";
					leaf deeperleaf {
						type string;
						description "";
					}

					list verydeeplist {
						key akey;
						description "";

						leaf akey {
							type string;
							description "";
						}
					}
				}

				list listinlist {
					key lilkey;
					leaf lilkey {
						type string;
					}
					leaf boringleaf {
						type string;
					}
					list listinlistinlist {
						key lilkey;
						leaf lilkey {
							type string;
						}
						leaf boringleaf {
							type string;
						}
					}
				}
			}
		}

		container typetester {
			leaf tint8 {
				type int8;
			}
			leaf tuint8 {
				type uint8;
			}
			leaf tint16 {
				type int16;
			}
			leaf tuint16 {
				type uint16;
			}
			leaf tint32 {
				type int32;
			}
			leaf tuint32 {
				type uint32;
			}
			leaf tint64 {
				type int64;
			}
			leaf tuint64 {
				type uint64;
			}
		}

		container acontainer {
			description "";
			container subcontainer {
				description "";
				leaf deepleaf {
					type uint8;
					description "";
				}
			}
		}

		leaf-list aleaflist {
			type string;
			description "";
		}

		leaf topleaf {
			type string;
		}

		leaf abitleaf {
			type bits {
				bit firstbit;
				bit secondbit;
			}
		}

		container usescontainer {
			description
				"";
			
			uses imp:agroup;
		}

		leaf abooleanleaf {
			type boolean;
		}

		leaf anemptyleaf {
			type empty;
		}

		leaf aunion {
			type union {
				type uint32;
				type string;
			}
		}

		leaf typedefleaf {
			type percent;
		}

        leaf typedefleaftwo {
            type name;
        }

		leaf enumtest {
			type enumeration {
				enum frib;
				enum frob;
				enum frab;			
			}
		}
        leaf-list sneakyleaflist {
            type enumeration {
                enum fee;
                enum fie;
                enum foe;
                enum fum;
            }
        }

	}
}
